# GNC_requirements

## AD-Sys-CL-06-1-CS-4: The control subsystem shall cope with wind and wind gusts of 55 [km/h] (Functional)

## AD-Sys-CL-02-1-CS-1: The drone shall be able to navigate without the intervention of the remote pilot on the control commands (Functional)

## AD-Sys-CL-02-2-CS-2: The drone shall be able to land and take-off without the intervention of the remote pilot on the control commands (Functional)

## AD-Sys-CL-02-2-CS-3: The drone shall be able to perform inspection routines without the intervention of the remote pilot on the control commands (Functional)

## AD-Sys-CL-07-1-CS-5: The control system shall provide the means for inspection module to be stationary with an accuracy of 5 [mm] w.r.t. the desired measurement point (Functional)

## AD-Sys-CL-07-1-CS-6: The relative position between drone and wind turbine shall be known with an accuracy of at least 5 [mm] (Functional)

## AD-Sys-CL-07-1-CS-7: Control system performance (Functional)
The control system shall provide the means for drone to have identical performance regardless of which inspection module is fitted, if any

## AD-Sys-CL-07-2-CS-8: The drone shall have a local navigation system with a range of 1 [m] (Functional)

## AD-Sys-CL-08-1-CS-9: The control system shall provide a change of path in order to avoid imminent collisions with obstacles (Functional)

## AD-Sys-CL-08-1-CS-10: The control system shall be able to predict if a collision is going to occur with an obstacle (Functional)

## AD-Sys-CL-08-4-CS-11: The control system shall be able to receive a manual command to trigger the FTS during automatic operations (Functional)

## AD-Sys-CL-08-9-CS-12: The control subsystem shall be able to stabilise the drone after an impact load of 3Ns (Functional)

## AD-Sys-CL-08-14-CS-14: The drone shall be able to determine geo-awareness state variables. (Functional)

## AD-Sys-CL-08-14-CS-15: The drone shall be able to determine its current fuel level (Functional)

## AD-Sys-CL-08-14-CS-18: The control subsystem shall facilitate immediate return to ground station in case reserve fuel level reaches 10% (Functional)

## AD-Sys-CL-08-14-CS-19: The drone shall not roll more than 60 deg (Functional)

## AD-Sys-CL-08-14-CS-19: The drone shall not pitch more than 60 deg (Functional)
