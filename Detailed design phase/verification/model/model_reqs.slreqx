# model_reqs

## Ver-DroMod-01: Motor response (Functional)
The drone model shall include a motor response estimation accurate within 0.001% error.

## Ver-DroMod-02: Normal force accuracy (Functional)
The drone model shall include a normal force estimation accurate within 0.001% error.

## Ver-DroMod-03: Gravity (Functional)
The drone model shall include a gravity force estimation accurate within 0.001%.

## Ver-DroMod-04: Airdrag (Functional)
The drone model shall include an airdrag force estimation accurate within 0.001%.
