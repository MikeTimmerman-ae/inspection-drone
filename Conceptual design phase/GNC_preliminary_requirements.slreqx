# GNC_preliminary_requirements

## Re-GNC-Prelim-01: The drone control system shall be robust (Functional)
- Rationale: The robustness requirement ensures that the control system is capable of regulating the system despite uncertainties in the system dynamics. This is essential considering the control system is designed based on linearized dynamics.

### Re-GNC-Prelim-01.1: The gain margin for the angular velocity feedback loop shall be infinite (Functional)
- Rationale: An infinite gain margin means that the control loop never becomes unstable, regardless of any amount of gain

### Re-GNC-Prelim-01.2: The gain margin for the attitude feedback loop shall be infinite (Functional)
- Rationale: An infinite gain margin means that the control loop never becomes unstable, regardless of any amount of gain

### Re-GNC-Prelim-01.3: The gain margin for the velocity feedback loop shall be more than 100dB (Functional)
- Rationale: A high gain margin ensure that the control system is capable of regulating the system while being able to handle system uncertainty

### Re-GNC-Prelim-01.4: The gain margin for the velocity feedback loop shall be more than 25dB (Functional)
- Rationale: A high gain margin ensure that the control system is capable of regulating the system while being able to handle system uncertainty

## Re-GNC-Prelim-02: The drone control system shall have a desirable performance (Functional)

### Re-GNC-Prelim-02.10: The drone shall not roll more than 60 deg (Functional)
- Rationale: Limiting the drone roll angle ensure desirable flying performance

### Re-GNC-Prelim-02.9: The drone shall not pitch more than 60 deg (Functional)
- Rationale: Limiting the drone pitch angle ensure desirable flying performance

### Re-GNC-Prelim-02.1: The cross-over frequency for the angular velocity feedback loop shall be 25 rad/s (+- 1%) (Functional)
- Rationale: A high cross-over frequency provide fast rise times, while not saturating actuators or amplifying noise by setting the cross-over frequency too high

### Re-GNC-Prelim-02.2: The cross-over frequency for the attitude feedback loop shall be 10 rad/s (+- 1%) (Functional)
- Rationale: A high cross-over frequency provide fast rise times, while not saturating actuators or amplifying noise by setting the cross-over frequency too high. Outer loops are also set to have a lower cross-over frequency than the inner loops.

### Re-GNC-Prelim-02.3: The cross-over frequency for the velocity feedback loop shall be 10 rad/s (+- 10%) (Functional)
- Rationale: A high cross-over frequency provide fast rise times, while not saturating actuators or amplifying noise by setting the cross-over frequency too high

### Re-GNC-Prelim-02.4: The cross-over frequency for the position feedback loop shall be 1 rad/s (+- 5%) (Functional)
- Rationale: A high cross-over frequency provide fast rise times, while not saturating actuators or amplifying noise by setting the cross-over frequency too high. Outer loops are also set to have a lower cross-over frequency than the inner loops

### Re-GNC-Prelim-02.5: The angular velocity feedback loop shall have 0% overshoot (Functional)
- Rationale: A small overshoot leads to desirable control system performance

### Re-GNC-Prelim-02.6: The attitude feedback loop shall have less than 10% overshoot (Functional)
- Rationale: A small overshoot leads to desirable control system performance

### Re-GNC-Prelim-02.7: The velocity feedback loop shall have less than 10% overshoot (Functional)
- Rationale: A small overshoot leads to desirable control system performance

### Re-GNC-Prelim-02.8: The position feedback loop shall have less than 10% overshoot (Functional)
- Rationale: A small overshoot leads to desirable control system performance

## Re-GNC-Prelim-03: The control system shall be stable (Functional)

### Re-GNC-Prelim-03.1: The angular velocity feedback loop shall have positive phase and gain margin (Functional)
- Rationale: Positive gain margins indicate stability of the closed-loop system

### Re-GNC-Prelim-03.2: The attitude feedback loop shall have positive phase and gain margin (Functional)
- Rationale: Positive gain margins indicate stability of the closed-loop system

### Re-GNC-Prelim-03.3: The velocity feedback loop shall have positive phase and gain margin (Functional)
- Rationale: Positive gain margins indicate stability of the closed-loop system

### Re-GNC-Prelim-03.4: The position feedback loop shall have positive phase and gain margin (Functional)
- Rationale: Positive gain margins indicate stability of the closed-loop system
